package SharedTypesBarrel {
    import SysMLPrimitives::*;
    
    @SourceFile { :>> path = "packages/shared-types/src/index.ts"; }
    package SharedTypesExport {
        doc /* Barrel file re-exporting enums, entities, and API types for the monorepo. */
    }
}
